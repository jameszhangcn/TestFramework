module mavenir-{{.Values.nf.nfId}}-cim-config {
        namespace "urn:mavenir:ns:yang:cnp:cim:{{.Values.nf.nfId}}";

        prefix {{.Values.nf.nfId}}-cim;

        import ietf-inet-types { prefix inet; }

        import tailf-common { prefix tailf; }

        revision "2020-02-07" {
            description "Initial revision";
        }
        container cimConfig {
                tailf:callpoint configUpdate {
                            tailf:transaction-hook subtree;
                        }
                container lmaas {
                         leaf max_file_size_in_mb {
                                        type int32 {
                                        	range "1 .. 50";
                                        }
                                        mandatory true;
                                        description "Maximum file size in MB to truncate.";
                                }

                         leaf max_backup_files {
                                        type int32 {
                                        	range "1 .. 20";
                                        }
                                        mandatory true;
                                        description "Maximum Backup files to keep.";
                                }
                         leaf max_age {
                                        type int32 {
                                        	range "1 .. 30";
                                        }
                                        mandatory true;
                                        description "Max age to keep backup file in days";
                                }
                         leaf buffer_size {
                                        type int32 {
                                        	range "1000 .. 100000";
                                        }
                                        mandatory true;
                                        description "Buffer size before writing to file in Bytes.";
                                }
                         leaf flush_timeout {
                                        type int32 {
                                        	range "5 .. 30";
                                        }
                                        mandatory true;
                                        description "Buffer flush to file timeout in seconds.";
                                }
                         leaf enable_tcp {
                                        tailf:callpoint restartConfigUpdate {
                                                tailf:transaction-hook node;
                                        }
                                        type boolean;
                                        mandatory true;
                                        description "log type is tcp or file";
                                } 
                         leaf daemonset_push {
                                        tailf:callpoint restartConfigUpdate {
                                                tailf:transaction-hook node;
                                        }
                                        type boolean;
                                        mandatory true;
                                        description "On true pod will send data to the local daemonset";
                                }
                         leaf fluentbit_svc_url {
                                        tailf:callpoint restartConfigUpdate {
                                                tailf:transaction-hook node;
                                        }
                                        type string;
                                        mandatory true;
                                        description "Fluent bit service url";
                                }
                         leaf fluentbit_tcp_port {
                                        tailf:callpoint restartConfigUpdate {
                                                tailf:transaction-hook node;
                                        }
                                        type string;
                                        mandatory true;
                                        description "Fluent bit tcp listening port";
                                }
                                           
                } 
                
                container haaas{
                         leaf hb_interval {
                                        type int32 {
                                        	range "100 .. 500";
                                        }
                                        mandatory true;
                                        description "Heart beat interval in milli seconds.";
                                }
                         leaf hb_frequency {
                                        type int32{
                                        	range "1 .. 20";
                                        }
                                        mandatory true;
                                        description "Heart beat frequency as aInteger";
                                }
                         leaf ha_timeout {
                                        type int32 {
                                        	range "60 .. 120";
                                        }
                                        mandatory true;
                                        description "HA Timeout in seconds.";
                                }
              }
                container cim_settings {
                         leaf enable_kpi {
                                        type boolean;
                                        mandatory true;
                                        description "For promotheus metrics make kpi(key performance indecator) true.";
                                }
                         leaf-list kafka_brokers {
                        				   tailf:callpoint restartConfigUpdate {
                                                tailf:transaction-hook node;
                                        }
                                        type string;
                                        description "List of kafka brokers as url:port.";
                                }
                         leaf etcd_url {
                        				   tailf:callpoint restartConfigUpdate {
                                                tailf:transaction-hook node;
                                        }
                                        type string;
                                        mandatory true;
                                        description "ETCD Url in url:port format.";
                                }
                         leaf http2_enabled {
                        	               tailf:callpoint restartConfigUpdate {
                                                tailf:transaction-hook node;
                                        }
                                        type boolean;
                                        mandatory true;
                                        description "Enable if client needs HTTP2 support.";
                                }
                         leaf log_level {
                                        type enumeration {
                                                 enum INFO;
                                                 enum DEBUG;
                                                 enum ERROR;
                                                 enum WARNING;
                                                 enum EXCEPTION;
                                                 enum ALL;
                                            }
                                        mandatory true;
                                        description "Log Level for CIM to print. select all if want to print all levels.";
                                }
                         leaf cim_file_log {
                                        type boolean;
                                        mandatory true;
                                        description "Enable if CIM needs to maintain own log file for CIM.";
                                }
                         leaf num_garp_count {
                                        type int32 {
                                        	range "0 .. 5";
                                        }
                                        mandatory true;
                                        description "Number of gratuitous arp packet sent [0-5]";
                                }
              }
                        
                container app_settings {
            	             leaf app_port {
                                        type int32 {
                                        	range "5000 .. 10000";
                                        }
                                        mandatory true;
                                        description "Port to communicate with Application.";
                                }
                         leaf enable_logs {
                                        type boolean;
                                        mandatory true;
                                        description "Enable for LOG subject activity at CIM.";
                                }
                         leaf enable_config {
                                        type boolean;
                                        mandatory true;
                                        description "Enable for CONFIG subject activity at CIM.";
                                }
                         leaf enable_event {
                                        type boolean;
                                        mandatory true;
                                        description "Enable for EVENT subject activity at CIM.";
                                }
                         leaf enable_trl {
                                        type boolean;
                                        mandatory true;
                                        description "Enable for TRL subject activity at CIM.";
                                }
                         leaf enable_cdr {
                                        type boolean;
                                        mandatory true;
                                        description "Enable for CDR subject activity at CIM.";
                                }
              }
        }
}
