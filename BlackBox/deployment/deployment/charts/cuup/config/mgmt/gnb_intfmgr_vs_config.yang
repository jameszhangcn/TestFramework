module gnb_intfmgr_vs_config {
	yang-version 1.1;

    namespace "urn:mavenir:ns:yang:cuup:intfmgrcfg";
    prefix "gnbIntfmgrVsConfig";

    revision 2020-05-08 {
        description "Initial revision.";
    }

    grouping intfmgrVsConfigGrp {
            leaf gnbCuUpNamePresent {
                type boolean;
                mandatory true;
                description "Whether gnbCuUpName Present";
            }

            leaf gnbCuUpName {
                type string {
                    length "1..150";
                }
                mandatory false;
                description "Human readable name of the gNB-CU-UP";
            }

            leaf cnSupported {
                type enumeration {
                    enum EPC;
                    enum 5GC;
                    enum both;
                }
                mandatory true;
                description "cnSupport: ENUMERATED (EPC. 5GC, both, …)";
            }

            leaf upE1SetupMaxRetryNum {
                type uint32{
                    range "0..5"; 
                }
                mandatory true;
                description "The maximum retry number for CU-UP E1 Setup request";
            }

            leaf assoEstabTimerExpiry {
                type uint32{
                    range "0..120";
                }
                mandatory true;
                description "The timer length for association establishment procedure.
                If the timer expires, the whole procedure will end";
            }

            leaf upE1SetupTimerExpiry {
                type uint32{
                    range "0..120";
                }
                mandatory true;
                description "The timer length for CU-UP E1 Setup request.  
                If the timer expires, a retry will be invoked if not reach maximum retry number";
            }	

            leaf gnbCuUpCapacityPresent {
                type boolean;
                mandatory true;
                description "Whether gnbCuUpCapacity present";
            }

            leaf gnbCuUpCapacity {
                type uint32{
                    range "0..255";
                }
                mandatory false;
                description "It indicates the relative processing capacity of an 
                gNB-CU-UP with respect to other gNB-CU-UPs in order to load-balance among different gNB-CU-UPs";
            }		
    }
}
