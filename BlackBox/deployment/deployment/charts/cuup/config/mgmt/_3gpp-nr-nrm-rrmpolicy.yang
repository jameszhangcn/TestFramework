module _3gpp-nr-nrm-rrmpolicy {
  yang-version 1.1;
  namespace "urn:3gpp:sa5:3gpp-nr-nrm-nrnetwork-rrmpolicy";
  prefix "nrrrmpolicy3gpp";

  import _3gpp-common-yang-types { prefix types3gpp; }
  import _3gpp-common-top { prefix top3gpp; }
  import mavenir_data_container { prefix mavenir;}

  organization "3GPP SA5";
  description "Defines the YANG mapping of the RRMPolicy abstract class that is part of the NR Network Resource Model (NRM).";
  reference "3GPP TS 28.541 5G Network Resource Model (NRM)";

 revision 2020-02-14 {
    description "Initial revision";
  }


  grouping rRMPolicyMemberGrp {
    description "This data type represents an RRM Policy member that will be part of a
      rRMPolicyMemberList. A RRMPolicyMember is defined by its pLMNId and sNSSAI (S-NSSAI).
      The members in a rRMPolicyMemberList are assigned a specific amount of RRM resources
      based on settings in RRMPolicy.";
    uses types3gpp:PLMNId;
    leaf sNSSAI {
      type types3gpp:SNssai;
    }
  }

  typedef QuotaType { 
    type enumeration  {
      enum STRICT;
      enum FLOAT;
    }
  }

  typedef CyclicPrefix {
    type enumeration {
      enum NORMAL;
      enum EXTENDED; 
    }
  }

  grouping RRMPolicy_Grp {
    description "This IOC represents the properties of an abstract RRMPolicy. The RRMPolicy_ IOC
      needs to be subclassed to be instantiated. It defines two attributes apart from those
      inherited from Top IOC, the resourceType attribute defines type of resource (PRB, RRC
      connected users, DRB usage etc.) and the rRMPolicyMemberList attribute defines the
      RRMPolicyMember(s)that are subject to this policy. An RRM resource (defined in resourceType
      attribute) is located in NRCellDU, NRCellCU, GNBDUFunction, GNBCUCPFunction or in
      GNBCUUPFunction. The RRMPolicyRatio IOC is one realization of a RRMPolicy_ IOC, see the
      inheritance in TS 28.541 Figure 4.2.1.2-1. This RRM framework allows adding new policies,
      both standardized (like RRMPolicyRatio) or as vendor specific, by inheriting from the
      abstract RRMPolicy_ IOC.";
    leaf resourceType {
      description "The resourceType attribute defines type of resource (PRB, RRC connected users,
      DRB usage etc.) that is subject to policy. Valid values are 'PRB', 'RRC' or 'DRB'";
      mandatory true;
      type string;
    }

    list rRMPolicyMemberList{
      description "It represents the list of RRMPolicyMember (s) that the managed object
        is supporting. A RRMPolicyMember <<dataType>> include the PLMNId <<dataType>> 
        and S-NSSAI <<dataType>>." ;
      min-elements 1;
      key "idx";
      leaf idx { type uint32; }
      uses rRMPolicyMemberGrp;
    }
  } // grouping


  grouping RRMPolicyRatioGrp {
    description "Represents the RRMPolicyRatio concrete IOC.";

    uses RRMPolicy_Grp;    // Inherits RRMPolicy_

    leaf quotaType {
      description "The type of the quota which allows to allocate resources as
        strictly usable for defined slice(s) (strict quota) or allows that
        resources to be used by other slice(s) when defined slice(s) do not
        need them (float quota).";
      mandatory true;
      type QuotaType;
    }

    leaf rRMPolicyMaxRatio {
      description "The RRM policy setting the maximum percentage of radio
        resources to be allocated to the corresponding S-NSSAI list. This
        quota can be strict or float quota. Strict quota means resources are
        not allowed for other sNSSAIs even when they are not used by the
        defined sNSSAIList. Float quota resources can be used by other sNSSAIs
        when the defined sNSSAIList do not need them. Value 0 indicates that
        there is no maximum limit.";
      mandatory true;
      type uint8 { range "0..100"; }
      units percent;
    }

    leaf rRMPolicyMarginMaxRatio {
      description "Maximum quota margin ratio is applicable when maximum quota
        policy ratio is of type float quota. It defines the resource quota
        within maximum quota to reserve buffers for new resource requirements
        for the specified S-NSSAI list. With the margin ratio, unused resources
        of the maximum resource quota can be allocated to other S-NSSAIs when
        the free resources are more than resource amount indicated by the
        margin. The margin resource quota can only be used for the specific
        S-NSSAI list. Value 0 indicates that no margin is used.";
      type uint8 { range "0..100"; }
      units percent;
    }

    leaf rRMPolicyMinRatio {
      description "The RRM policy setting the minimum percentage of radio
        resources to be allocated to the corresponding S-NSSAI list. This
        quota can be strict or float quota. Strict quota means resources are
        not allowed for other sNSSAIs even when they are not used by the
        defined sNSSAIList. Float quota resources can be used by other sNSSAIs
        when the defined sNSSAIList do not need them. Value 0 indicates that
        there is no minimum limit.";
      mandatory true;
      type uint8 { range "0..100"; }
      units percent;
    }

    leaf rRMPolicyMarginMinRatio {
      description "Minimum quota margin ratio is applicable when minimum quota
        policy ratio is of type float quota. It defines the resource quota
        within minimum quota to reserve buffers for new resource requirements
        for the specified S-NSSAI list. With the margin ratio, unused resources
        of the minimum resource quota can be allocated to other S-NSSAIs when
        the free resources are more than resource amount indicated by the
        margin. The margin resource quota can only be used for the specific
        S-NSSAI list. Value 0 indicates that no margin is used. Value 0
        indicates that there is no minimum limit.";
      type uint8 { range "0..100"; }
      units percent;
      }
    }
  augment /mavenir:data {
  list RRMPolicyRatio {
    description " The RRMPolicyRatio IOC is one realization of a RRMPolicy_ IOC, see the
      inheritance in Figure 4.2.1.2-1. This RRM framework allows adding new policies, both
      standardized (like RRMPolicyRatio) or as vendor specific, by inheriting from the 
      abstract RRMPolicy_ IOC. For details see subclause 4.3.36.";
    key id;
    uses top3gpp:Top_Grp;
    container attributes {
      uses RRMPolicyRatioGrp;
    }
  }
}

}
